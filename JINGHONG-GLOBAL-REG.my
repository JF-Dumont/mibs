--
-- JINGHONG-GLOBAL-REG.my
-- MIB generated by MG-SOFT Visual MIB Builder Version 6.0  Build 88
-- Sunday, April 20, 2014 at 13:53:17
--

--  JINGHONG-GLOBAL-REG.my
-- MIB generated by MG-SOFT Visual MIB Builder Version 6.0  Build 88
-- Friday, February 14, 2014 at 10:14:54
-- 
--  JINGHONG-GLOBAL-REG.my
-- MIB generated by MG-SOFT Visual MIB Builder Version 6.0  Build 88
-- Wednesday, February 12, 2014 at 11:46:11
-- 
--  JINGHONG-GLOBAL-REG.my
-- MIB generated by MG-SOFT Visual MIB Builder Version 6.0  Build 88
-- Wednesday, February 12, 2014 at 10:05:22
-- 
--  JINGHONG-GLOBAL-REG.my
-- MIB generated by MG-SOFT Visual MIB Builder Version 6.0  Build 88
-- Monday, September 23, 2013 at 09:40:24
-- 
--  JINGHONG-GLOBAL-REG.my
-- MIB generated by MG-SOFT Visual MIB Builder Version 6.0  Build 88
-- Monday, July 29, 2013 at 09:32:15
-- 

	JINGHONG-GLOBAL-REG DEFINITIONS ::= BEGIN
 
		IMPORTS
			enterprises, TimeTicks, IpAddress, Integer32, OBJECT-TYPE			
				FROM SNMPv2-SMI;
	
	
--
-- Node definitions
--
	
		-- 1.3.6.1.4.1.35626
		jhCmtsRoot OBJECT IDENTIFIER ::= { enterprises 35626 }

		
		-- 1.3.6.1.4.1.35626.1
		jhCmtsMibGroup OBJECT IDENTIFIER ::= { jhCmtsRoot 1 }

		
		-- 1.3.6.1.4.1.35626.1.1
		jhIpGroup OBJECT IDENTIFIER ::= { jhCmtsMibGroup 1 }

		
		-- 1.3.6.1.4.1.35626.1.1.1
		jhCpeClassTable OBJECT-TYPE
			SYNTAX SEQUENCE OF JhCpeClassEntry
			MAX-ACCESS not-accessible
			STATUS current
			DESCRIPTION
				"Description."
			::= { jhIpGroup 1 }

		
		-- 1.3.6.1.4.1.35626.1.1.1.1
		jhCpeClassEntry OBJECT-TYPE
			SYNTAX JhCpeClassEntry
			MAX-ACCESS not-accessible
			STATUS current
			DESCRIPTION
				"Description."
			INDEX { jhCpeClassIndex }
			::= { jhCpeClassTable 1 }

		
		JhCpeClassEntry ::=
			SEQUENCE { 
				jhCpeClassIndex
					Integer32,
				jhCpeClassIpIndex
					Integer32,
				jhCpeClassString
					OCTET STRING,
				jhCpeClassRowStatus
					INTEGER
			 }

		-- 1.3.6.1.4.1.35626.1.1.1.1.1
		jhCpeClassIndex OBJECT-TYPE
			SYNTAX Integer32 (1..63335)
			MAX-ACCESS read-write
			STATUS current
			DESCRIPTION
				"索引"
			::= { jhCpeClassEntry 1 }

		
		-- 1.3.6.1.4.1.35626.1.1.1.1.2
		jhCpeClassIpIndex OBJECT-TYPE
			SYNTAX Integer32
			MAX-ACCESS read-write
			STATUS current
			DESCRIPTION
				"jhIpTable中的Index"
			::= { jhCpeClassEntry 2 }

		
		-- 1.3.6.1.4.1.35626.1.1.1.1.3
		jhCpeClassString OBJECT-TYPE
			SYNTAX OCTET STRING
			MAX-ACCESS read-write
			STATUS current
			DESCRIPTION
				"Option 60 文本"
			::= { jhCpeClassEntry 3 }

		
		-- 1.3.6.1.4.1.35626.1.1.1.1.4
		jhCpeClassRowStatus OBJECT-TYPE
			SYNTAX INTEGER
				{
				active(1),
				notInService(2),
				notReady(3),
				createAndGo(4),
				createAndWait(5),
				destroy(6)
				}
			MAX-ACCESS read-write
			STATUS current
			DESCRIPTION
				"行状态
				-active（1），表明状态行是可用的
				-notInService（2），表明行存在但不可用
				-notReady（3），表明存在，但因为缺少必要的信息而不能用
				-createAndGo（4），有管理者设置，表明希望创建一个概念行并设置该行的状态列对象为active
				-createAndWait（5），有管理者设置，表明希望创建一个概念行，但不可用
				-destroy（6），删除行"
			::= { jhCpeClassEntry 4 }

		
		-- 1.3.6.1.4.1.35626.1.1.2
		jhIpTable OBJECT-TYPE
			SYNTAX SEQUENCE OF JhIpEntry
			MAX-ACCESS not-accessible
			STATUS current
			DESCRIPTION
				"CMTS IP表，表示CMTS设备本身拥有的IP地址。可以通过这些IP地址访问到设备。"
			::= { jhIpGroup 2 }

		
		-- 1.3.6.1.4.1.35626.1.1.2.1
		jhIpEntry OBJECT-TYPE
			SYNTAX JhIpEntry
			MAX-ACCESS not-accessible
			STATUS current
			DESCRIPTION
				"Description."
			INDEX { jhIpIndex }
			::= { jhIpTable 1 }

		
		JhIpEntry ::=
			SEQUENCE { 
				jhIpIndex
					Integer32,
				jhIpType
					Integer32,
				jhIpIpAddress
					IpAddress,
				jhIpMask
					IpAddress,
				jhIpRowStatus
					INTEGER
			 }

		-- 1.3.6.1.4.1.35626.1.1.2.1.1
		jhIpIndex OBJECT-TYPE
			SYNTAX Integer32 (1..255)
			MAX-ACCESS read-only
			STATUS current
			DESCRIPTION
				"索引"
			::= { jhIpEntry 1 }

		
		-- 1.3.6.1.4.1.35626.1.1.2.1.2
		jhIpType OBJECT-TYPE
			SYNTAX Integer32
			MAX-ACCESS read-write
			STATUS current
			DESCRIPTION
				"用于设备IP地址用途。
				1 cmts CMTS IP地址
				2 cm   表示此IP地址提供给CM使用
				3 cpe  表示此IP地址提供给CPE使用
				4 mta  表示此IP地址提供给MTA使用
				5 second (cmts 第2个IP） 表示CMTS的第二个IP地址，此TYPE可在表中重复(其余Type不可重复)
				6 cpe-class1 
				7 cpe-class2
				.
				.
				.
				n cpe-class(n-5)"
			::= { jhIpEntry 2 }

		
		-- 1.3.6.1.4.1.35626.1.1.2.1.3
		jhIpIpAddress OBJECT-TYPE
			SYNTAX IpAddress
			MAX-ACCESS read-write
			STATUS current
			DESCRIPTION
				"IP地址"
			::= { jhIpEntry 3 }

		
		-- 1.3.6.1.4.1.35626.1.1.2.1.4
		jhIpMask OBJECT-TYPE
			SYNTAX IpAddress
			MAX-ACCESS read-write
			STATUS current
			DESCRIPTION
				"网关"
			::= { jhIpEntry 4 }

		
		-- 1.3.6.1.4.1.35626.1.1.2.1.5
		jhIpRowStatus OBJECT-TYPE
			SYNTAX INTEGER
				{
				active(1),
				notInService(2),
				notReady(3),
				createAndGo(4),
				createAndWait(5),
				destroy(6)
				}
			MAX-ACCESS read-write
			STATUS current
			DESCRIPTION
				"行状态
				-active（1），表明状态行是可用的
				-notInService（2），表明行存在但不可用
				-notReady（3），表明存在，但因为缺少必要的信息而不能用
				-createAndGo（4），有管理者设置，表明希望创建一个概念行并设置该行的状态列对象为active
				-createAndWait（5），有管理者设置，表明希望创建一个概念行，但不可用
				-destroy（6），删除行"
			::= { jhIpEntry 5 }

		
		-- 1.3.6.1.4.1.35626.1.2
		jhRouteGroup OBJECT IDENTIFIER ::= { jhCmtsMibGroup 2 }

		
		-- 1.3.6.1.4.1.35626.1.2.1
		jhRouteTable OBJECT-TYPE
			SYNTAX SEQUENCE OF JhRouteEntry
			MAX-ACCESS not-accessible
			STATUS current
			DESCRIPTION
				"CMTS 路由表。"
			::= { jhRouteGroup 1 }

		
		-- 1.3.6.1.4.1.35626.1.2.1.1
		jhRouteEntry OBJECT-TYPE
			SYNTAX JhRouteEntry
			MAX-ACCESS not-accessible
			STATUS current
			DESCRIPTION
				"Description."
			INDEX { jhRouteIndex }
			::= { jhRouteTable 1 }

		
		JhRouteEntry ::=
			SEQUENCE { 
				jhRouteIndex
					Integer32,
				jhRouteIpAddress
					IpAddress,
				jhRouterMask
					IpAddress,
				jhRouteGetway
					IpAddress,
				jhRouteRowStatus
					INTEGER
			 }

		-- 1.3.6.1.4.1.35626.1.2.1.1.1
		jhRouteIndex OBJECT-TYPE
			SYNTAX Integer32 (1..255)
			MAX-ACCESS read-write
			STATUS current
			DESCRIPTION
				"Description."
			::= { jhRouteEntry 1 }

		
		-- 1.3.6.1.4.1.35626.1.2.1.1.2
		jhRouteIpAddress OBJECT-TYPE
			SYNTAX IpAddress
			MAX-ACCESS read-write
			STATUS current
			DESCRIPTION
				"Description."
			::= { jhRouteEntry 2 }

		
		-- 1.3.6.1.4.1.35626.1.2.1.1.3
		jhRouterMask OBJECT-TYPE
			SYNTAX IpAddress
			MAX-ACCESS read-write
			STATUS current
			DESCRIPTION
				"Description."
			::= { jhRouteEntry 3 }

		
		-- 1.3.6.1.4.1.35626.1.2.1.1.4
		jhRouteGetway OBJECT-TYPE
			SYNTAX IpAddress
			MAX-ACCESS read-write
			STATUS current
			DESCRIPTION
				"网关地址"
			::= { jhRouteEntry 4 }

		
		-- 1.3.6.1.4.1.35626.1.2.1.1.5
		jhRouteRowStatus OBJECT-TYPE
			SYNTAX INTEGER
				{
				active(1),
				notInService(2),
				notReady(3),
				createAndGo(4),
				createAndWait(5),
				destroy(6)
				}
			MAX-ACCESS read-write
			STATUS current
			DESCRIPTION
				"Description."
			::= { jhRouteEntry 5 }

		
		-- 1.3.6.1.4.1.35626.1.2.3
		jhPolicyRouteTable OBJECT-TYPE
			SYNTAX SEQUENCE OF JhPolicyRouteEntry
			MAX-ACCESS not-accessible
			STATUS current
			DESCRIPTION
				"策略路由表"
			::= { jhRouteGroup 3 }

		
		-- 1.3.6.1.4.1.35626.1.2.3.1
		jhPolicyRouteEntry OBJECT-TYPE
			SYNTAX JhPolicyRouteEntry
			MAX-ACCESS not-accessible
			STATUS current
			DESCRIPTION
				"Description."
			INDEX { jhRouteIndex }
			::= { jhPolicyRouteTable 1 }

		
		JhPolicyRouteEntry ::=
			SEQUENCE { 
				jhPolicyIndex
					Integer32,
				jhPolicynetRouteIp
					IpAddress,
				jhPolicyrouteMask
					IpAddress,
				jhPolicyGwIp
					IpAddress,
				jhPolicyRowStatus
					INTEGER
			 }

		-- 1.3.6.1.4.1.35626.1.2.3.1.1
		jhPolicyIndex OBJECT-TYPE
			SYNTAX Integer32
			MAX-ACCESS read-write
			STATUS current
			DESCRIPTION
				"Description."
			::= { jhPolicyRouteEntry 1 }

		
		-- 1.3.6.1.4.1.35626.1.2.3.1.2
		jhPolicynetRouteIp OBJECT-TYPE
			SYNTAX IpAddress
			MAX-ACCESS read-write
			STATUS current
			DESCRIPTION
				"Description."
			::= { jhPolicyRouteEntry 2 }

		
		-- 1.3.6.1.4.1.35626.1.2.3.1.3
		jhPolicyrouteMask OBJECT-TYPE
			SYNTAX IpAddress
			MAX-ACCESS read-write
			STATUS current
			DESCRIPTION
				"Description."
			::= { jhPolicyRouteEntry 3 }

		
		-- 1.3.6.1.4.1.35626.1.2.3.1.4
		jhPolicyGwIp OBJECT-TYPE
			SYNTAX IpAddress
			MAX-ACCESS read-write
			STATUS current
			DESCRIPTION
				"Description."
			::= { jhPolicyRouteEntry 4 }

		
		-- 1.3.6.1.4.1.35626.1.2.3.1.5
		jhPolicyRowStatus OBJECT-TYPE
			SYNTAX INTEGER
				{
				active(1),
				notInService(2),
				notReady(3),
				createAndGo(4),
				createAndWait(5),
				destroy(6)
				}
			MAX-ACCESS read-write
			STATUS current
			DESCRIPTION
				"Description."
			::= { jhPolicyRouteEntry 5 }

		
		-- 1.3.6.1.4.1.35626.1.3
		jhNetGroup OBJECT IDENTIFIER ::= { jhCmtsMibGroup 3 }

		
		-- 1.3.6.1.4.1.35626.1.3.1
		netModeCm OBJECT-TYPE
			SYNTAX Integer32 (0..1)
			MAX-ACCESS read-write
			STATUS current
			DESCRIPTION
				"CM网络模式 2 二层 3 三层"
			::= { jhNetGroup 1 }

		
		-- 1.3.6.1.4.1.35626.1.3.2
		netModeCpe OBJECT-TYPE
			SYNTAX Integer32 (0..1)
			MAX-ACCESS read-write
			STATUS current
			DESCRIPTION
				"PC网络模式 2 二层 3 三层"
			::= { jhNetGroup 2 }

		
		-- 1.3.6.1.4.1.35626.1.3.3
		jhHelperTable OBJECT-TYPE
			SYNTAX SEQUENCE OF JhHelperEntry
			MAX-ACCESS not-accessible
			STATUS current
			DESCRIPTION
				"Description."
			::= { jhNetGroup 3 }

		
		-- 1.3.6.1.4.1.35626.1.3.3.1
		jhHelperEntry OBJECT-TYPE
			SYNTAX JhHelperEntry
			MAX-ACCESS not-accessible
			STATUS current
			DESCRIPTION
				"Description."
			INDEX { jhHelperIndex }
			::= { jhHelperTable 1 }

		
		JhHelperEntry ::=
			SEQUENCE { 
				jhHelperIndex
					Integer32,
				jhHelperType
					Integer32,
				jhHelperIpAddress
					IpAddress,
				jhHelperRowStatus
					INTEGER
			 }

		-- 1.3.6.1.4.1.35626.1.3.3.1.1
		jhHelperIndex OBJECT-TYPE
			SYNTAX Integer32 (1..256)
			MAX-ACCESS read-write
			STATUS current
			DESCRIPTION
				"索引"
			::= { jhHelperEntry 1 }

		
		-- 1.3.6.1.4.1.35626.1.3.3.1.2
		jhHelperType OBJECT-TYPE
			SYNTAX Integer32
			MAX-ACCESS read-write
			STATUS current
			DESCRIPTION
				"1:默认地址
				2:CM
				3:cpe
				4:mta
				6:cpe class1
				7:cpe class2"
			::= { jhHelperEntry 2 }

		
		-- 1.3.6.1.4.1.35626.1.3.3.1.3
		jhHelperIpAddress OBJECT-TYPE
			SYNTAX IpAddress
			MAX-ACCESS read-write
			STATUS current
			DESCRIPTION
				"Description."
			::= { jhHelperEntry 3 }

		
		-- 1.3.6.1.4.1.35626.1.3.3.1.4
		jhHelperRowStatus OBJECT-TYPE
			SYNTAX INTEGER
				{
				active(1),
				notInService(2),
				notReady(3),
				createAndGo(4),
				createAndWait(5),
				destroy(6)
				}
			MAX-ACCESS read-write
			STATUS current
			DESCRIPTION
				"Description."
			::= { jhHelperEntry 4 }

		
		-- 1.3.6.1.4.1.35626.1.3.4
		relayCmts OBJECT-TYPE
			SYNTAX Integer32 (0..1)
			MAX-ACCESS read-write
			STATUS current
			DESCRIPTION
				"CMTS DHCP中继开关，1：打开 2：关闭"
			::= { jhNetGroup 4 }

		
		-- 1.3.6.1.4.1.35626.1.3.5
		option82Switch OBJECT-TYPE
			SYNTAX Integer32 (0..1)
			MAX-ACCESS read-write
			STATUS current
			DESCRIPTION
				"DHCP option 82(中继代理)开关.1:打开 2:关闭"
			::= { jhNetGroup 5 }

		
		-- 1.3.6.1.4.1.35626.1.3.6
		l2VpnSwitch OBJECT-TYPE
			SYNTAX Integer32 (0..1)
			MAX-ACCESS read-write
			STATUS current
			DESCRIPTION
				"L2VPN开关：1 打开 2 关闭
				
				功能注释：
				MPLS L2VPN就是在MPLS网络上透明传输用户二层数据。
				从用户的角度来看，MPLS网络是一个二层交换网络，可以在不同节点间建立二层连接。"
			::= { jhNetGroup 6 }

		
		-- 1.3.6.1.4.1.35626.1.3.7
		loopbackSwitch OBJECT-TYPE
			SYNTAX Integer32 (0..1)
			MAX-ACCESS read-write
			STATUS current
			DESCRIPTION
				"内网互访开关：1 打开 2 关闭"
			::= { jhNetGroup 7 }

		
		-- 1.3.6.1.4.1.35626.1.3.8
		ipSnoopSwitch OBJECT-TYPE
			SYNTAX Integer32 (0..1)
			MAX-ACCESS read-write
			STATUS current
			DESCRIPTION
				"IP原地址检查开关。1:打开 2:关闭"
			::= { jhNetGroup 8 }

		
		-- 1.3.6.1.4.1.35626.1.3.9
		rebootCmts OBJECT-TYPE
			SYNTAX Integer32 (1)
			MAX-ACCESS read-write
			STATUS current
			DESCRIPTION
				"1:重启CMTS"
			::= { jhNetGroup 9 }

		
		-- 1.3.6.1.4.1.35626.1.3.10
		saveConfig OBJECT-TYPE
			SYNTAX Integer32 (1..3)
			MAX-ACCESS read-write
			STATUS current
			DESCRIPTION
				"1:保存配置
				2:应用下行通道配置
				3:应用上行通道配置"
			::= { jhNetGroup 10 }

		
		-- 1.3.6.1.4.1.35626.1.4
		jhAclMibGroup OBJECT IDENTIFIER ::= { jhCmtsMibGroup 4 }

		
		-- 1.3.6.1.4.1.35626.1.4.1
		jhAclTable OBJECT-TYPE
			SYNTAX SEQUENCE OF JhAclEntry
			MAX-ACCESS not-accessible
			STATUS current
			DESCRIPTION
				"此表功能暂时未实现，现预留。"
			::= { jhAclMibGroup 1 }

		
		-- 1.3.6.1.4.1.35626.1.4.1.1
		jhAclEntry OBJECT-TYPE
			SYNTAX JhAclEntry
			MAX-ACCESS not-accessible
			STATUS current
			DESCRIPTION
				"Description."
			INDEX { jhAclIndex }
			::= { jhAclTable 1 }

		
		JhAclEntry ::=
			SEQUENCE { 
				jhAclIndex
					Integer32,
				jhAclIp
					IpAddress,
				jhAclMask
					IpAddress,
				jhAclRowStatus
					INTEGER
			 }

		-- 1.3.6.1.4.1.35626.1.4.1.1.1
		jhAclIndex OBJECT-TYPE
			SYNTAX Integer32 (1..256)
			MAX-ACCESS read-write
			STATUS current
			DESCRIPTION
				"Description."
			::= { jhAclEntry 1 }

		
		-- 1.3.6.1.4.1.35626.1.4.1.1.2
		jhAclIp OBJECT-TYPE
			SYNTAX IpAddress
			MAX-ACCESS read-write
			STATUS current
			DESCRIPTION
				"Description."
			::= { jhAclEntry 2 }

		
		-- 1.3.6.1.4.1.35626.1.4.1.1.3
		jhAclMask OBJECT-TYPE
			SYNTAX IpAddress
			MAX-ACCESS read-write
			STATUS current
			DESCRIPTION
				"Description."
			::= { jhAclEntry 3 }

		
		-- 1.3.6.1.4.1.35626.1.4.1.1.4
		jhAclRowStatus OBJECT-TYPE
			SYNTAX INTEGER
				{
				active(1),
				notInService(2),
				notReady(3),
				createAndGo(4),
				createAndWait(5),
				destroy(6)
				}
			MAX-ACCESS read-write
			STATUS current
			DESCRIPTION
				"
				-active（1），表明状态行是可用的
				-notInService（2），表明行存在但不可用
				-notReady（3），表明存在，但因为缺少必要的信息而不能用
				-createAndGo（4），有管理者设置，表明希望创建一个概念行并设置该行的状态列对象为active
				-createAndWait（5），有管理者设置，表明希望创建一个概念行，但不可用
				-destroy（6），删除行"
			::= { jhAclEntry 4 }

		
		-- 1.3.6.1.4.1.35626.1.5
		jhFlapGroup OBJECT IDENTIFIER ::= { jhCmtsMibGroup 5 }

		
		-- 1.3.6.1.4.1.35626.1.5.1
		jhFlapTable OBJECT-TYPE
			SYNTAX SEQUENCE OF JhFlapEntry
			MAX-ACCESS not-accessible
			STATUS current
			DESCRIPTION
				"Description."
			::= { jhFlapGroup 1 }

		
		-- 1.3.6.1.4.1.35626.1.5.1.1
		jhFlapEntry OBJECT-TYPE
			SYNTAX JhFlapEntry
			MAX-ACCESS not-accessible
			STATUS current
			DESCRIPTION
				"Description."
			INDEX { cmMac }
			::= { jhFlapTable 1 }

		
		JhFlapEntry ::=
			SEQUENCE { 
				cmIns
					Integer32,
				cmHit
					Integer32,
				cmMiss
					Integer32,
				cmCrc
					Integer32,
				cmPdj
					Integer32,
				cmFlap
					Integer32,
				cmFlapDate
					Integer32,
				cmFlapTime
					Integer32,
				cmMac
					OCTET STRING,
				cmCpe
					OCTET STRING
			 }

		-- 1.3.6.1.4.1.35626.1.5.1.1.1
		cmIns OBJECT-TYPE
			SYNTAX Integer32
			MAX-ACCESS read-write
			STATUS current
			DESCRIPTION
				"Description."
			::= { jhFlapEntry 1 }

		
		-- 1.3.6.1.4.1.35626.1.5.1.1.2
		cmHit OBJECT-TYPE
			SYNTAX Integer32
			MAX-ACCESS read-write
			STATUS current
			DESCRIPTION
				"Description."
			::= { jhFlapEntry 2 }

		
		-- 1.3.6.1.4.1.35626.1.5.1.1.3
		cmMiss OBJECT-TYPE
			SYNTAX Integer32
			MAX-ACCESS read-write
			STATUS current
			DESCRIPTION
				"Description."
			::= { jhFlapEntry 3 }

		
		-- 1.3.6.1.4.1.35626.1.5.1.1.4
		cmCrc OBJECT-TYPE
			SYNTAX Integer32
			MAX-ACCESS read-write
			STATUS current
			DESCRIPTION
				"Description."
			::= { jhFlapEntry 4 }

		
		-- 1.3.6.1.4.1.35626.1.5.1.1.5
		cmPdj OBJECT-TYPE
			SYNTAX Integer32
			MAX-ACCESS read-write
			STATUS current
			DESCRIPTION
				"Description."
			::= { jhFlapEntry 5 }

		
		-- 1.3.6.1.4.1.35626.1.5.1.1.6
		cmFlap OBJECT-TYPE
			SYNTAX Integer32
			MAX-ACCESS read-write
			STATUS current
			DESCRIPTION
				"Description."
			::= { jhFlapEntry 6 }

		
		-- 1.3.6.1.4.1.35626.1.5.1.1.7
		cmFlapDate OBJECT-TYPE
			SYNTAX Integer32
			MAX-ACCESS read-write
			STATUS current
			DESCRIPTION
				"Description."
			::= { jhFlapEntry 7 }

		
		-- 1.3.6.1.4.1.35626.1.5.1.1.8
		cmFlapTime OBJECT-TYPE
			SYNTAX Integer32
			MAX-ACCESS read-write
			STATUS current
			DESCRIPTION
				"Description."
			::= { jhFlapEntry 8 }

		
		-- 1.3.6.1.4.1.35626.1.5.1.1.9
		cmMac OBJECT-TYPE
			SYNTAX OCTET STRING
			MAX-ACCESS read-write
			STATUS current
			DESCRIPTION
				"Description."
			::= { jhFlapEntry 9 }

		
		-- 1.3.6.1.4.1.35626.1.5.1.1.10
		cmCpe OBJECT-TYPE
			SYNTAX OCTET STRING
			MAX-ACCESS read-write
			STATUS current
			DESCRIPTION
				"Description."
			::= { jhFlapEntry 10 }

		
		-- 1.3.6.1.4.1.35626.1.6
		jhEmbedDHCPMibGroup OBJECT IDENTIFIER ::= { jhCmtsMibGroup 6 }

		
		-- 1.3.6.1.4.1.35626.1.6.1
		jhDHCPScopeMibGroup OBJECT IDENTIFIER ::= { jhEmbedDHCPMibGroup 1 }

		
		-- 1.3.6.1.4.1.35626.1.6.1.1
		jhDHCPScopeTable OBJECT-TYPE
			SYNTAX SEQUENCE OF JhDHCPScopeEntry
			MAX-ACCESS not-accessible
			STATUS current
			DESCRIPTION
				"Description."
			::= { jhDHCPScopeMibGroup 1 }

		
		-- 1.3.6.1.4.1.35626.1.6.1.1.1
		jhDHCPScopeEntry OBJECT-TYPE
			SYNTAX JhDHCPScopeEntry
			MAX-ACCESS not-accessible
			STATUS current
			DESCRIPTION
				"Description."
			INDEX { jhDHCPScopeIndex }
			::= { jhDHCPScopeTable 1 }

		
		JhDHCPScopeEntry ::=
			SEQUENCE { 
				jhDHCPScopeIndex
					Integer32,
				jhScopeType
					Integer32,
				jhStartIp
					IpAddress,
				jhEndIp
					IpAddress,
				jhSubMask
					IpAddress,
				jhGatewayIp
					IpAddress,
				jhFirstDNS
					IpAddress,
				jhSecondDNS
					IpAddress,
				jhReleaseTime
					Integer32,
				jhTftpServer
					IpAddress,
				jhTftpFile
					OCTET STRING
			 }

		-- 1.3.6.1.4.1.35626.1.6.1.1.1.1
		jhDHCPScopeIndex OBJECT-TYPE
			SYNTAX Integer32 (1..256)
			MAX-ACCESS read-write
			STATUS current
			DESCRIPTION
				"Description."
			::= { jhDHCPScopeEntry 1 }

		
		-- 1.3.6.1.4.1.35626.1.6.1.1.1.2
		jhScopeType OBJECT-TYPE
			SYNTAX Integer32
			MAX-ACCESS read-write
			STATUS current
			DESCRIPTION
				"1:默认地址
				2:CM
				3:cpe
				4:mta
				6:cpe class1
				7:cpe class2"
			::= { jhDHCPScopeEntry 2 }

		
		-- 1.3.6.1.4.1.35626.1.6.1.1.1.3
		jhStartIp OBJECT-TYPE
			SYNTAX IpAddress
			MAX-ACCESS read-write
			STATUS current
			DESCRIPTION
				"Description."
			::= { jhDHCPScopeEntry 3 }

		
		-- 1.3.6.1.4.1.35626.1.6.1.1.1.4
		jhEndIp OBJECT-TYPE
			SYNTAX IpAddress
			MAX-ACCESS read-write
			STATUS current
			DESCRIPTION
				"Description."
			::= { jhDHCPScopeEntry 4 }

		
		-- 1.3.6.1.4.1.35626.1.6.1.1.1.5
		jhSubMask OBJECT-TYPE
			SYNTAX IpAddress
			MAX-ACCESS read-write
			STATUS current
			DESCRIPTION
				"Description."
			::= { jhDHCPScopeEntry 5 }

		
		-- 1.3.6.1.4.1.35626.1.6.1.1.1.6
		jhGatewayIp OBJECT-TYPE
			SYNTAX IpAddress
			MAX-ACCESS read-write
			STATUS current
			DESCRIPTION
				"Description."
			::= { jhDHCPScopeEntry 6 }

		
		-- 1.3.6.1.4.1.35626.1.6.1.1.1.7
		jhFirstDNS OBJECT-TYPE
			SYNTAX IpAddress
			MAX-ACCESS read-write
			STATUS current
			DESCRIPTION
				"Description."
			::= { jhDHCPScopeEntry 7 }

		
		-- 1.3.6.1.4.1.35626.1.6.1.1.1.8
		jhSecondDNS OBJECT-TYPE
			SYNTAX IpAddress
			MAX-ACCESS read-write
			STATUS current
			DESCRIPTION
				"Description."
			::= { jhDHCPScopeEntry 8 }

		
		-- 1.3.6.1.4.1.35626.1.6.1.1.1.9
		jhReleaseTime OBJECT-TYPE
			SYNTAX Integer32
			MAX-ACCESS read-write
			STATUS current
			DESCRIPTION
				"Description."
			::= { jhDHCPScopeEntry 9 }

		
		-- 1.3.6.1.4.1.35626.1.6.1.1.1.10
		jhTftpServer OBJECT-TYPE
			SYNTAX IpAddress
			MAX-ACCESS read-write
			STATUS current
			DESCRIPTION
				"Description."
			::= { jhDHCPScopeEntry 10 }

		
		-- 1.3.6.1.4.1.35626.1.6.1.1.1.11
		jhTftpFile OBJECT-TYPE
			SYNTAX OCTET STRING
			MAX-ACCESS read-write
			STATUS current
			DESCRIPTION
				"Description."
			::= { jhDHCPScopeEntry 11 }

		
		-- 1.3.6.1.4.1.35626.1.6.2
		jhDHCPStaticIpGroup OBJECT IDENTIFIER ::= { jhEmbedDHCPMibGroup 2 }

		
		-- 1.3.6.1.4.1.35626.1.6.2.1
		jhDHCPStaticIpTable OBJECT-TYPE
			SYNTAX SEQUENCE OF JhDHCPStaticIpEntry
			MAX-ACCESS not-accessible
			STATUS current
			DESCRIPTION
				"Description."
			::= { jhDHCPStaticIpGroup 1 }

		
		-- 1.3.6.1.4.1.35626.1.6.2.1.1
		jhDHCPStaticIpEntry OBJECT-TYPE
			SYNTAX JhDHCPStaticIpEntry
			MAX-ACCESS not-accessible
			STATUS current
			DESCRIPTION
				"Description."
			INDEX { jhDHCPStaticIpIndex }
			::= { jhDHCPStaticIpTable 1 }

		
		JhDHCPStaticIpEntry ::=
			SEQUENCE { 
				jhDHCPStaticIpIndex
					Integer32,
				jhDHCPStaticIpAddress
					IpAddress,
				jhDHCPStaticIpMac
					OCTET STRING,
				jhDHCPStaticIpRowStatus
					Integer32
			 }

		-- 1.3.6.1.4.1.35626.1.6.2.1.1.1
		jhDHCPStaticIpIndex OBJECT-TYPE
			SYNTAX Integer32 (1..256)
			MAX-ACCESS read-write
			STATUS current
			DESCRIPTION
				"Description."
			::= { jhDHCPStaticIpEntry 1 }

		
		-- 1.3.6.1.4.1.35626.1.6.2.1.1.2
		jhDHCPStaticIpAddress OBJECT-TYPE
			SYNTAX IpAddress
			MAX-ACCESS read-write
			STATUS current
			DESCRIPTION
				"Description."
			::= { jhDHCPStaticIpEntry 2 }

		
		-- 1.3.6.1.4.1.35626.1.6.2.1.1.3
		jhDHCPStaticIpMac OBJECT-TYPE
			SYNTAX OCTET STRING
			MAX-ACCESS read-write
			STATUS current
			DESCRIPTION
				"Description."
			::= { jhDHCPStaticIpEntry 3 }

		
		-- 1.3.6.1.4.1.35626.1.6.2.1.1.4
		jhDHCPStaticIpRowStatus OBJECT-TYPE
			SYNTAX Integer32
			MAX-ACCESS read-write
			STATUS current
			DESCRIPTION
				"Description."
			::= { jhDHCPStaticIpEntry 4 }

		
		-- 1.3.6.1.4.1.35626.1.7
		jhLogGroup OBJECT IDENTIFIER ::= { jhCmtsMibGroup 7 }

		
		-- 1.3.6.1.4.1.35626.1.7.1
		jhLogTable OBJECT-TYPE
			SYNTAX SEQUENCE OF JhLogEntry
			MAX-ACCESS not-accessible
			STATUS current
			DESCRIPTION
				"记录设备日志信息表"
			::= { jhLogGroup 1 }

		
		-- 1.3.6.1.4.1.35626.1.7.1.1
		jhLogEntry OBJECT-TYPE
			SYNTAX JhLogEntry
			MAX-ACCESS not-accessible
			STATUS current
			DESCRIPTION
				"Description."
			INDEX { jhLogIndex }
			::= { jhLogTable 1 }

		
		JhLogEntry ::=
			SEQUENCE { 
				jhLogIndex
					Integer32,
				jhHelperLogTime
					TimeTicks,
				jhHelperLogMessage
					OCTET STRING
			 }

		-- 1.3.6.1.4.1.35626.1.7.1.1.1
		jhLogIndex OBJECT-TYPE
			SYNTAX Integer32 (1..65335)
			MAX-ACCESS read-write
			STATUS current
			DESCRIPTION
				"Description."
			::= { jhLogEntry 1 }

		
		-- 1.3.6.1.4.1.35626.1.7.1.1.2
		jhHelperLogTime OBJECT-TYPE
			SYNTAX TimeTicks
			MAX-ACCESS read-write
			STATUS current
			DESCRIPTION
				"日志产生时间"
			::= { jhLogEntry 2 }

		
		-- 1.3.6.1.4.1.35626.1.7.1.1.3
		jhHelperLogMessage OBJECT-TYPE
			SYNTAX OCTET STRING
			MAX-ACCESS read-write
			STATUS current
			DESCRIPTION
				"日志内容"
			::= { jhLogEntry 3 }

		
		-- 1.3.6.1.4.1.35626.1.8
		jhIfBaseObjects OBJECT IDENTIFIER ::= { jhCmtsMibGroup 8 }

		
		-- 1.3.6.1.4.1.35626.1.8.1
		jhIfDownstreamChannelTable OBJECT-TYPE
			SYNTAX SEQUENCE OF JhIfDownstreamChannelEntry
			MAX-ACCESS not-accessible
			STATUS current
			DESCRIPTION
				"Description."
			::= { jhIfBaseObjects 1 }

		
		-- 1.3.6.1.4.1.35626.1.8.1.1
		jhIfDownstreamChannelEntry OBJECT-TYPE
			SYNTAX JhIfDownstreamChannelEntry
			MAX-ACCESS not-accessible
			STATUS current
			DESCRIPTION
				"Description."
			INDEX { jhIfDownChannelId }
			::= { jhIfDownstreamChannelTable 1 }

		
		JhIfDownstreamChannelEntry ::=
			SEQUENCE { 
				jhIfDownChannelId
					Integer32,
				jhIfDownChannelStatus
					Integer32,
				jhIfDownChannelUsageRates
					Integer32
			 }

		-- 1.3.6.1.4.1.35626.1.8.1.1.1
		jhIfDownChannelId OBJECT-TYPE
			SYNTAX Integer32 (1..10000)
			MAX-ACCESS read-only
			STATUS current
			DESCRIPTION
				"Description."
			::= { jhIfDownstreamChannelEntry 1 }

		
		-- 1.3.6.1.4.1.35626.1.8.1.1.2
		jhIfDownChannelStatus OBJECT-TYPE
			SYNTAX Integer32
			MAX-ACCESS read-write
			STATUS current
			DESCRIPTION
				"Description."
			::= { jhIfDownstreamChannelEntry 2 }

		
		-- 1.3.6.1.4.1.35626.1.8.1.1.3
		jhIfDownChannelUsageRates OBJECT-TYPE
			SYNTAX Integer32
			MAX-ACCESS read-only
			STATUS current
			DESCRIPTION
				"Description."
			::= { jhIfDownstreamChannelEntry 3 }

		
		-- 1.3.6.1.4.1.35626.1.8.2
		jhIfUpstreamChannelTable OBJECT-TYPE
			SYNTAX SEQUENCE OF JhIfUpstreamChannelEntry
			MAX-ACCESS not-accessible
			STATUS current
			DESCRIPTION
				"Description."
			::= { jhIfBaseObjects 2 }

		
		-- 1.3.6.1.4.1.35626.1.8.2.1
		jhIfUpstreamChannelEntry OBJECT-TYPE
			SYNTAX JhIfUpstreamChannelEntry
			MAX-ACCESS not-accessible
			STATUS current
			DESCRIPTION
				"Description."
			INDEX { jhIfUpChannelId }
			::= { jhIfUpstreamChannelTable 1 }

		
		JhIfUpstreamChannelEntry ::=
			SEQUENCE { 
				jhIfUpChannelId
					Integer32,
				jhIfUpChannelStatus
					Integer32,
				jhIfUpChannelUsageRates
					Integer32,
				jhIfUpChannelCmAll
					Integer32,
				jhIfUpChannelCmOnline
					Integer32,
				jhIfUpChannelCmOffline
					Integer32
			 }

		-- 1.3.6.1.4.1.35626.1.8.2.1.1
		jhIfUpChannelId OBJECT-TYPE
			SYNTAX Integer32 (1..10000)
			MAX-ACCESS read-only
			STATUS current
			DESCRIPTION
				"Description."
			::= { jhIfUpstreamChannelEntry 1 }

		
		-- 1.3.6.1.4.1.35626.1.8.2.1.2
		jhIfUpChannelStatus OBJECT-TYPE
			SYNTAX Integer32
			MAX-ACCESS read-write
			STATUS current
			DESCRIPTION
				"Description."
			::= { jhIfUpstreamChannelEntry 2 }

		
		-- 1.3.6.1.4.1.35626.1.8.2.1.3
		jhIfUpChannelUsageRates OBJECT-TYPE
			SYNTAX Integer32
			MAX-ACCESS read-only
			STATUS current
			DESCRIPTION
				"Description."
			::= { jhIfUpstreamChannelEntry 3 }

		
		-- 1.3.6.1.4.1.35626.1.8.2.1.4
		jhIfUpChannelCmAll OBJECT-TYPE
			SYNTAX Integer32
			MAX-ACCESS read-only
			STATUS current
			DESCRIPTION
				"Description."
			::= { jhIfUpstreamChannelEntry 4 }

		
		-- 1.3.6.1.4.1.35626.1.8.2.1.5
		jhIfUpChannelCmOnline OBJECT-TYPE
			SYNTAX Integer32
			MAX-ACCESS read-only
			STATUS current
			DESCRIPTION
				"Description."
			::= { jhIfUpstreamChannelEntry 5 }

		
		-- 1.3.6.1.4.1.35626.1.8.2.1.6
		jhIfUpChannelCmOffline OBJECT-TYPE
			SYNTAX Integer32
			MAX-ACCESS read-only
			STATUS current
			DESCRIPTION
				"Description."
			::= { jhIfUpstreamChannelEntry 6 }

		
		-- 1.3.6.1.4.1.35626.1.8.3
		cmAll OBJECT-TYPE
			SYNTAX Integer32 (0..65225)
			MAX-ACCESS read-only
			STATUS current
			DESCRIPTION
				"Description."
			::= { jhIfBaseObjects 3 }

		
		-- 1.3.6.1.4.1.35626.1.8.4
		cmOnline OBJECT-TYPE
			SYNTAX Integer32 (0..65225)
			MAX-ACCESS read-only
			STATUS current
			DESCRIPTION
				"Description."
			::= { jhIfBaseObjects 4 }

		
		-- 1.3.6.1.4.1.35626.1.8.5
		cmOffline OBJECT-TYPE
			SYNTAX Integer32 (0..65525)
			MAX-ACCESS read-only
			STATUS current
			DESCRIPTION
				"Description."
			::= { jhIfBaseObjects 5 }

		
		-- 1.3.6.1.4.1.35626.1.9
		jhEntityPhysical OBJECT IDENTIFIER ::= { jhCmtsMibGroup 9 }

		
		-- 1.3.6.1.4.1.35626.1.9.1
		jhEntityVoltageTable OBJECT-TYPE
			SYNTAX SEQUENCE OF JhEntityVoltageEntry
			MAX-ACCESS not-accessible
			STATUS current
			DESCRIPTION
				"Description."
			::= { jhEntityPhysical 1 }

		
		-- 1.3.6.1.4.1.35626.1.9.1.1
		jhEntityVoltageEntry OBJECT-TYPE
			SYNTAX JhEntityVoltageEntry
			MAX-ACCESS not-accessible
			STATUS current
			DESCRIPTION
				"Description."
			INDEX { jhEntityVoltageIndex }
			::= { jhEntityVoltageTable 1 }

		
		JhEntityVoltageEntry ::=
			SEQUENCE { 
				jhEntityVoltageIndex
					Integer32,
				jhEntityVoltageDesr
					Integer32,
				jhEntityVoltageValue
					Integer32
			 }

		-- 1.3.6.1.4.1.35626.1.9.1.1.1
		jhEntityVoltageIndex OBJECT-TYPE
			SYNTAX Integer32 (1..65535)
			MAX-ACCESS read-only
			STATUS current
			DESCRIPTION
				"Description."
			::= { jhEntityVoltageEntry 1 }

		
		-- 1.3.6.1.4.1.35626.1.9.1.1.2
		jhEntityVoltageDesr OBJECT-TYPE
			SYNTAX Integer32
			MAX-ACCESS read-write
			STATUS current
			DESCRIPTION
				"Description."
			::= { jhEntityVoltageEntry 2 }

		
		-- 1.3.6.1.4.1.35626.1.9.1.1.3
		jhEntityVoltageValue OBJECT-TYPE
			SYNTAX Integer32
			MAX-ACCESS read-write
			STATUS current
			DESCRIPTION
				"Description."
			::= { jhEntityVoltageEntry 3 }

		
		-- 1.3.6.1.4.1.35626.1.9.2
		jhEntityTempTable OBJECT-TYPE
			SYNTAX SEQUENCE OF JhEntityTempEntry
			MAX-ACCESS not-accessible
			STATUS current
			DESCRIPTION
				"Description."
			::= { jhEntityPhysical 2 }

		
		-- 1.3.6.1.4.1.35626.1.9.2.1
		jhEntityTempEntry OBJECT-TYPE
			SYNTAX JhEntityTempEntry
			MAX-ACCESS not-accessible
			STATUS current
			DESCRIPTION
				"Description."
			INDEX { jhEntityTempIndex }
			::= { jhEntityTempTable 1 }

		
		JhEntityTempEntry ::=
			SEQUENCE { 
				jhEntityTempIndex
					Integer32,
				jhEntityTempDesr
					Integer32,
				jhEntityTempValue
					Integer32
			 }

		-- 1.3.6.1.4.1.35626.1.9.2.1.1
		jhEntityTempIndex OBJECT-TYPE
			SYNTAX Integer32 (1..65535)
			MAX-ACCESS read-only
			STATUS current
			DESCRIPTION
				"Description."
			::= { jhEntityTempEntry 1 }

		
		-- 1.3.6.1.4.1.35626.1.9.2.1.2
		jhEntityTempDesr OBJECT-TYPE
			SYNTAX Integer32
			MAX-ACCESS read-write
			STATUS current
			DESCRIPTION
				"Description."
			::= { jhEntityTempEntry 2 }

		
		-- 1.3.6.1.4.1.35626.1.9.2.1.3
		jhEntityTempValue OBJECT-TYPE
			SYNTAX Integer32
			MAX-ACCESS read-write
			STATUS current
			DESCRIPTION
				"Description."
			::= { jhEntityTempEntry 3 }

		
		-- 1.3.6.1.4.1.35626.1.10
		jhTrap OBJECT IDENTIFIER ::= { jhCmtsMibGroup 10 }

		
		-- 1.3.6.1.4.1.35626.1.10.1
		jhIpaTrapTable OBJECT-TYPE
			SYNTAX SEQUENCE OF JhIpaTrapEntry
			MAX-ACCESS not-accessible
			STATUS current
			DESCRIPTION
				"Description."
			::= { jhTrap 1 }

		
		-- 1.3.6.1.4.1.35626.1.10.1.1
		jhIpaTrapEntry OBJECT-TYPE
			SYNTAX JhIpaTrapEntry
			MAX-ACCESS not-accessible
			STATUS current
			DESCRIPTION
				"Description."
			INDEX { jhIpaTrapIndex }
			::= { jhIpaTrapTable 1 }

		
		JhIpaTrapEntry ::=
			SEQUENCE { 
				jhIpaTrapIndex
					Integer32,
				jhIpaTrapIp
					IpAddress,
				jhIpaTrapCommunity
					OCTET STRING,
				jhIpaTrapStatus
					INTEGER
			 }

		-- 1.3.6.1.4.1.35626.1.10.1.1.1
		jhIpaTrapIndex OBJECT-TYPE
			SYNTAX Integer32 (1..10)
			MAX-ACCESS read-only
			STATUS current
			DESCRIPTION
				"Tarp服务器索引."
			::= { jhIpaTrapEntry 1 }

		
		-- 1.3.6.1.4.1.35626.1.10.1.1.2
		jhIpaTrapIp OBJECT-TYPE
			SYNTAX IpAddress
			MAX-ACCESS read-write
			STATUS current
			DESCRIPTION
				"Trap服务器地址"
			::= { jhIpaTrapEntry 2 }

		
		-- 1.3.6.1.4.1.35626.1.10.1.1.3
		jhIpaTrapCommunity OBJECT-TYPE
			SYNTAX OCTET STRING
			MAX-ACCESS read-write
			STATUS current
			DESCRIPTION
				"Trap共同体."
			::= { jhIpaTrapEntry 3 }

		
		-- 1.3.6.1.4.1.35626.1.10.1.1.4
		jhIpaTrapStatus OBJECT-TYPE
			SYNTAX INTEGER
				{
				active(1),
				notInService(2),
				notReady(3),
				createAndGo(4),
				createAndWait(5),
				destroy(6)
				}
			MAX-ACCESS read-write
			STATUS current
			DESCRIPTION
				"Trap行状态"
			::= { jhIpaTrapEntry 4 }

		
	
	END

--
-- JINGHONG-GLOBAL-REG.my
--
